(vl-load-com)

(defun cdr:replace-all (new old value / pos start)
  (if (null value) (setq value ""))
  (setq start 0)
  (while (setq pos (vl-string-search old value start))
    (setq value (vl-string-subst new old value pos))
    (setq start (+ pos (strlen new)))
  )
  value
)

(defun cdr:json-string (value / text)
  (cond
    ((null value) (setq text ""))
    ((= (type value) 'STR) (setq text value))
    (T (setq text (vl-princ-to-string value)))
  )
  (setq text (cdr:replace-all "\\\\" "\\" text))
  (setq text (cdr:replace-all "\\\"" "\"" text))
  (setq text (cdr:replace-all "\\r" "\r" text))
  (setq text (cdr:replace-all "\\n" "\n" text))
  (setq text (cdr:replace-all "\\t" "\t" text))
  (strcat "\"" text "\"")
)

(defun cdr:number (value)
  (if (numberp value) (rtos (float value) 2 6) "null")
)

(defun cdr:code-array (value / result separator code)
  (if (null value) (setq value ""))
  (setq result "[" separator "")
  (foreach code (vl-string->list value)
    (setq result (strcat result separator (itoa code)))
    (setq separator ",")
  )
  (strcat result "]")
)

(defun cdr:bbox-from-data (entity-type data / xs ys pair code value radius count)
  (setq count 0)
  (foreach pair data
    (setq code (car pair) value (cdr pair))
    (if (and (< count 64) (>= code 10) (<= code 18) (listp value))
      (progn
        (setq xs (cons (car value) xs))
        (setq ys (cons (cadr value) ys))
        (setq count (1+ count))
      )
    )
  )
  (if (and xs ys)
    (progn
      (if (and (member entity-type '("CIRCLE" "ARC")) (assoc 40 data))
        (progn
          (setq radius (abs (cdr (assoc 40 data))))
          (setq xs (append (list (- (car xs) radius) (+ (car xs) radius)) xs))
          (setq ys (append (list (- (car ys) radius) (+ (car ys) radius)) ys))
        )
      )
      (list (apply 'min xs) (apply 'min ys) (apply 'max xs) (apply 'max ys))
    )
    nil
  )
)

(defun cdr:collect-text (entity-type data / value text pair)
  (cond
    ((member entity-type '("TEXT" "ATTRIB" "ATTDEF"))
      (if (assoc 1 data) (cdr (assoc 1 data)) ""))
    ((= entity-type "MTEXT")
      (setq text "")
      (foreach pair data
        (if (member (car pair) '(1 3)) (setq text (strcat text (cdr pair))))
      )
      text)
    ((= entity-type "DIMENSION")
      (if (assoc 1 data) (cdr (assoc 1 data)) ""))
    (T "")
  )
)

(defun cdr:block-name (entity-type data / value)
  (if (= entity-type "INSERT")
    (if (assoc 2 data) (cdr (assoc 2 data)) "")
    ""
  )
)

(defun cdr:shape-signature (entity-type data bbox / first-point result pair code value dx dy point-count property-count)
  (setq result "")
  (setq point-count 0 property-count 0)
  (foreach pair data
    (setq code (car pair) value (cdr pair))
    (cond
      ((and (< point-count 24) (>= code 10) (<= code 18) (listp value))
        (if (null first-point) (setq first-point value))
        (setq dx (- (car value) (car first-point)))
        (setq dy (- (cadr value) (cadr first-point)))
        (setq result (strcat result (itoa code) ":" (rtos dx 2 4) "," (rtos dy 2 4) ";"))
        (setq point-count (1+ point-count))
      )
      ((and (< property-count 48) (member code '(40 41 42 43 44 45 46 47 48 50 51 52 53 70 71 72 73 74 75 90 91)))
        (setq result (strcat result (itoa code) ":" (vl-princ-to-string value) ";"))
        (setq property-count (1+ property-count))
      )
    )
  )
  (if bbox
    (strcat
      (rtos (- (nth 2 bbox) (nth 0 bbox)) 2 4) "x"
      (rtos (- (nth 3 bbox) (nth 1 bbox)) 2 4) "|" result)
    result
  )
)

(defun cdr:write-entity (stream entity space-name / data entity-type handle layer text block bbox x y width height rotation measurement text-height shape line)
  (progn
      (setq data (entget entity))
      (setq entity-type (if (assoc 0 data) (cdr (assoc 0 data)) "UNKNOWN"))
      (setq handle (if (assoc 5 data) (cdr (assoc 5 data)) ""))
      (setq layer (if (assoc 8 data) (cdr (assoc 8 data)) ""))
      (setq text (cdr:collect-text entity-type data))
      (setq block (cdr:block-name entity-type data))
      (setq bbox (cdr:bbox-from-data entity-type data))
      (if bbox
        (progn
          (setq x (/ (+ (nth 0 bbox) (nth 2 bbox)) 2.0))
          (setq y (/ (+ (nth 1 bbox) (nth 3 bbox)) 2.0))
          (setq width (- (nth 2 bbox) (nth 0 bbox)))
          (setq height (- (nth 3 bbox) (nth 1 bbox)))
        )
        (setq x nil y nil width nil height nil)
      )
      (setq rotation (if (assoc 50 data) (cdr (assoc 50 data)) nil))
      (setq measurement (if (assoc 42 data) (cdr (assoc 42 data)) nil))
      (setq text-height (if (and (member entity-type '("TEXT" "MTEXT" "ATTRIB" "ATTDEF")) (assoc 40 data)) (cdr (assoc 40 data)) nil))
      (setq shape (cdr:shape-signature entity-type data bbox))
      (setq line
        (strcat
          "{\"handle\":" (cdr:json-string handle)
          ",\"type\":" (cdr:json-string entity-type)
          ",\"layer_codes\":" (cdr:code-array layer)
          ",\"space_codes\":" (cdr:code-array space-name)
          ",\"text_codes\":" (cdr:code-array text)
          ",\"block_codes\":" (cdr:code-array block)
          ",\"x\":" (cdr:number x)
          ",\"y\":" (cdr:number y)
          ",\"width\":" (cdr:number width)
          ",\"height\":" (cdr:number height)
          ",\"rotation\":" (cdr:number rotation)
          ",\"measurement\":" (cdr:number measurement)
          ",\"text_height\":" (cdr:number text-height)
          ",\"shape\":" (cdr:json-string shape)
          "}"
        )
      )
      (write-line line stream)
  )
)

(defun cdr:export-facts (output-path / block-record block-name flags block-entity entity entity-type stream count selection index data layout-name)
  (setq stream (open output-path "w"))
  (if (null stream)
    (progn (princ "\nFACT_EXPORT_ERROR=OPEN_FAILED") nil)
    (progn
      (setq count 0)
      (setq selection (ssget "_X"))
      (if selection
        (progn
          (setq index 0)
          (repeat (sslength selection)
            (setq entity (ssname selection index))
            (setq data (entget entity))
            (setq layout-name (if (assoc 410 data) (cdr (assoc 410 data)) "Model"))
            (if (= (strcase layout-name) "MODEL")
              (setq layout-name "*Model_Space")
              (setq layout-name (strcat "Layout:" layout-name))
            )
            (cdr:write-entity stream entity layout-name)
            (setq count (1+ count))
            (setq index (1+ index))
          )
        )
      )
      (setq block-record (tblnext "BLOCK" T))
      (while block-record
        (setq block-name (cdr (assoc 2 block-record)))
        (setq flags (if (assoc 70 block-record) (cdr (assoc 70 block-record)) 0))
        (if (and
              (= 0 (logand flags 12))
              (or (/= (substr block-name 1 1) "*") (= (substr block-name 1 (min 2 (strlen block-name))) "*U"))
            )
          (progn
            (setq block-entity (tblobjname "BLOCK" block-name))
            (setq entity (entnext block-entity))
            (while entity
              (setq entity-type (cdr (assoc 0 (entget entity))))
              (if (= entity-type "ENDBLK")
                (setq entity nil)
                (progn
                  (cdr:write-entity stream entity block-name)
                  (setq count (1+ count))
                  (setq entity (entnext entity))
                )
              )
            )
          )
        )
        (setq block-record (tblnext "BLOCK"))
      )
      (close stream)
      (princ (strcat "\nFACT_EXPORT_COUNT=" (itoa count)))
      count
    )
  )
)

(princ)
