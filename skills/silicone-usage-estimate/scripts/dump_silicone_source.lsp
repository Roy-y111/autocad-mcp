(vl-load-com)
(defun sc-outdir ( / d)
  (setq d (getenv "SILICONE_OUT_DIR"))
  (if (and d (/= d ""))
    (strcat d "/")
    (strcat (getenv "USERPROFILE") "/Desktop/CL_CAD/outputs/")))

(defun sc-list (v)
  (cond ((= (type v) 'VARIANT) (sc-list (vlax-variant-value v)))
        ((= (type v) 'SAFEARRAY) (vlax-safearray->list v))
        ((listp v) v)
        (t nil)))
(defun sc-num (n) (rtos n 2 6))
(defun sc-join (nums / s)
  (setq s "")
  (foreach n nums (setq s (strcat s (if (= s "") "" ",") (sc-num n))))
  s)
(defun sc-prop (o p / r)
  (setq r (vl-catch-all-apply 'vlax-get-property (list o p)))
  (if (vl-catch-all-error-p r) nil r))
(defun sc-err (msg / ef)
  (setq ef (open (strcat (sc-outdir) "silicone_source_error.txt") "w"))
  (if ef (progn (write-line msg ef) (close ef)))
  (princ))
(defun c:SCDUMPSOURCE (/ *error* doc ms f o typ lay bn pt ats a tag coords color width sp ep)
  (setq *error* 'sc-err)
  (setq f (open (strcat (sc-outdir) "silicone_source.txt") "w"))
  (setq doc (vla-get-ActiveDocument (vlax-get-acad-object)) ms (vla-get-ModelSpace doc))
  (vlax-for o ms
    (setq typ (vla-get-ObjectName o) lay (vla-get-Layer o))
    (cond
      ((= typ "AcDbBlockReference")
       (setq bn (sc-prop o 'EffectiveName))
       (if (not bn) (setq bn (vla-get-Name o)))
       (if (member bn '("_LCNo001" "_LDNO001" "_LOPN001"))
         (progn
           (setq pt (sc-list (vla-get-InsertionPoint o)))
           (if (= :vlax-true (vla-get-HasAttributes o))
             (progn
               (setq ats (vlax-invoke o 'GetAttributes))
               (foreach a ats
                 (setq tag (strcase (vla-get-TagString a)))
                 (if (member tag '("NO" "U"))
                   (write-line (strcat "TAG|" (vla-get-TextString a) "|" (sc-num (car pt)) "|" (sc-num (cadr pt))) f))))))))
      ((and (= typ "AcDbPolyline") (= lay "OPEN"))
       (setq color (vla-get-Color o) width (sc-prop o 'ConstantWidth))
       (if (not (and (= color 1) width (equal width 2.0 0.01)))
         (progn
           (setq coords (sc-list (vla-get-Coordinates o)))
           (write-line (strcat "PL|" (if (= :vlax-true (vla-get-Closed o)) "1" "0") "|" (sc-join coords)) f))))
      ((and (= typ "AcDbLine") (= lay "OPEN"))
       (setq sp (sc-list (vla-get-StartPoint o)) ep (sc-list (vla-get-EndPoint o)))
       (setq coords (list (car sp) (cadr sp) (car ep) (cadr ep)))
       (write-line (strcat "PL|0|" (sc-join coords)) f))))
  (close f)
  (princ "\nSCDUMPSOURCE complete.")
  (princ))
