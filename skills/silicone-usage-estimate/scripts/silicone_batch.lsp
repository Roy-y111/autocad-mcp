(vl-load-com)

(defun scb-outdir ( / d)
  (setq d (getenv "SILICONE_OUT_DIR"))
  (if (and d (/= d ""))
    (strcat d "/")
    (strcat (getenv "USERPROFILE") "/Desktop/CL_CAD/outputs/")))

(defun scb-split (s delim / p out n)
  (setq out '() n (strlen delim))
  (while (setq p (vl-string-search delim s))
    (setq out (append out (list (substr s 1 p))))
    (setq s (substr s (+ p n 1))))
  (append out (list s)))

(defun scb-ray (pt dir obj / doc ms ray vals arr lst best p d i)
  (setq doc (vla-get-ActiveDocument (vlax-get-acad-object)))
  (setq ms (vla-get-ModelSpace doc))
  (setq ray (vla-AddRay ms (vlax-3d-point pt) (vlax-3d-point (mapcar '+ pt dir))))
  (setq vals (vl-catch-all-apply 'vla-IntersectWith (list obj ray acExtendNone)))
  (setq best nil d 1e99)
  (if (not (vl-catch-all-error-p vals))
    (progn
      (setq arr (vlax-variant-value vals))
      (if (>= (vlax-safearray-get-u-bound arr 1) 0)
        (progn
          (setq lst (vlax-safearray->list arr) i 0)
          (while (< i (length lst))
            (setq p (list (nth i lst) (nth (+ i 1) lst) (nth (+ i 2) lst)))
            (if (and (> (distance pt p) 1e-6) (< (distance pt p) d))
              (setq best p d (distance pt p)))
            (setq i (+ i 3)))))))
  (vla-delete ray)
  best)

(defun scb-erase-ss (ss / i)
  (if ss (progn (setq i 0) (repeat (sslength ss) (entdel (ssname ss i)) (setq i (1+ i))))))

(defun scb-error (msg)
  (if scb-file (close scb-file))
  (if scb-old-layer (setvar "CLAYER" scb-old-layer))
  (if scb-old-osmode (setvar "OSMODE" scb-old-osmode))
  (princ (strcat "\nSILBATCH error: " msg))
  (princ))

(defun c:SILBATCH (/ *error* doc ms lays lay in line p code pane x y ew eh pt ent obj l r u d minx maxx miny maxy w h perim status seen key)
  (setq *error* 'scb-error)
  (setq scb-old-layer (getvar "CLAYER") scb-old-osmode (getvar "OSMODE"))
  (setvar "OSMODE" 0)
  (setq doc (vla-get-ActiveDocument (vlax-get-acad-object)) ms (vla-get-ModelSpace doc))
  (setq lays (vla-get-Layers doc))
  (setq lay (vl-catch-all-apply 'vla-Item (list lays "SILICONE-CHECK")))
  (if (vl-catch-all-error-p lay) (setq lay (vla-Add lays "SILICONE-CHECK")))
  (vla-put-Color lay 1)

  ;; Cleanup only in the SiliconeCheck copy.
  (scb-erase-ss (ssget "_X" '((0 . "LWPOLYLINE") (8 . "C7-0"))))
  (scb-erase-ss (ssget "_X" '((0 . "ATTDEF") (2 . "FIX"))))
  (scb-erase-ss (ssget "_X" '((0 . "LWPOLYLINE") (62 . 1) (43 . 2.0))))

  (setvar "CLAYER" "SILICONE-CHECK")
  (setq in (open (strcat (scb-outdir) "silicone_seeds.txt") "r"))
  (setq scb-file (open (strcat (scb-outdir) "silicone_batch_result.csv") "w"))
  (write-line "Code,Pane,WidthCm,HeightCm,PerimeterCm,ExpectedW,ExpectedH,Status" scb-file)
  (setq seen '())
  (while (setq line (read-line in))
    (setq p (scb-split line "|"))
    (setq code (nth 0 p) pane (nth 1 p) x (atof (nth 2 p)) y (atof (nth 3 p)) ew (atof (nth 4 p)) eh (atof (nth 5 p)))
    (setq pt (list x y 0.0) status "BPOLY_FAIL" w 0.0 h 0.0 perim 0.0)
    (setq ent (bpoly pt))
    (if ent
      (progn
        (setq obj (vlax-ename->vla-object ent))
        (setq l (scb-ray pt '(-1.0 0.0 0.0) obj) r (scb-ray pt '(1.0 0.0 0.0) obj)
              u (scb-ray pt '(0.0 1.0 0.0) obj) d (scb-ray pt '(0.0 -1.0 0.0) obj))
        (if (and l r u d)
          (progn
            (setq minx (car l) maxx (car r) miny (cadr d) maxy (cadr u))
            (setq w (abs (- maxx minx)) h (abs (- maxy miny)) perim (* 2.0 (+ w h)))
            (entdel ent)
            (if (and (<= (abs (- w ew)) 2.0) (<= (abs (- h eh)) 2.0))
              (progn
                (setq key (strcat code "|" (rtos minx 2 2) "|" (rtos miny 2 2) "|" (rtos maxx 2 2) "|" (rtos maxy 2 2)))
                (if (not (member key seen))
                  (progn
                    (command "_.PLINE" "_NON" (list minx miny) "_NON" (list maxx miny) "_NON" (list maxx maxy) "_NON" (list minx maxy) "_C")
                    (setq obj (vlax-ename->vla-object (entlast)))
                    (vla-put-Layer obj "SILICONE-CHECK") (vla-put-Color obj 1)
                    (vl-catch-all-apply 'vla-put-ConstantWidth (list obj 2.0))
                    (setq seen (cons key seen) status "OK"))
                  (setq status "DUPLICATE")))
              (setq status "SIZE_MISMATCH")))
          (progn (entdel ent) (setq status "RAY_FAIL")))))
    (write-line (strcat code "," pane "," (rtos w 2 2) "," (rtos h 2 2) "," (rtos perim 2 2) "," (rtos ew 2 2) "," (rtos eh 2 2) "," status) scb-file))
  (close in) (close scb-file) (setq scb-file nil)
  (setvar "CLAYER" scb-old-layer) (setvar "OSMODE" scb-old-osmode)
  (princ "\nSILBATCH complete. Results on SILICONE-CHECK layer.")
  (princ))
