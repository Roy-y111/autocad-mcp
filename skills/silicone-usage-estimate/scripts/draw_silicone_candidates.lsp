(vl-load-com)
(defun scc-outdir ( / d)
  (setq d (getenv "SILICONE_OUT_DIR"))
  (if (and d (/= d ""))
    (strcat d "/")
    (strcat (getenv "USERPROFILE") "/Desktop/CL_CAD/outputs/")))

(defun scc-split (s d / p out n)
  (setq out '() n (strlen d))
  (while (setq p (vl-string-search d s))
    (setq out (append out (list (substr s 1 p))) s (substr s (+ p n 1))))
  (append out (list s)))
(defun scc-erase (ss / i) (if ss (progn (setq i 0) (repeat (sslength ss) (entdel (ssname ss i)) (setq i (1+ i))))))
(defun c:SILCANDIDATES (/ doc ms lays lay f line p code pane x y w h x0 x1 y0 y1 obj oldlay oldos)
  (setq oldlay (getvar "CLAYER") oldos (getvar "OSMODE")) (setvar "OSMODE" 0)
  (setq doc (vla-get-ActiveDocument (vlax-get-acad-object)) ms (vla-get-ModelSpace doc) lays (vla-get-Layers doc))
  (setq lay (vl-catch-all-apply 'vla-Item (list lays "SILICONE-CANDIDATE")))
  (if (vl-catch-all-error-p lay) (setq lay (vla-Add lays "SILICONE-CANDIDATE")))
  (vla-put-Color lay 2)
  (scc-erase (ssget "_X" '((8 . "SILICONE-CANDIDATE"))))
  (setvar "CLAYER" "SILICONE-CANDIDATE")
  (setq f (open (strcat (scc-outdir) "silicone_seeds.txt") "r"))
  (while (setq line (read-line f))
    (setq p (scc-split line "|") code (nth 0 p) pane (nth 1 p) x (atof (nth 2 p)) y (atof (nth 3 p)) w (atof (nth 4 p)) h (atof (nth 5 p)))
    (setq x0 (- x (/ w 2.0)) x1 (+ x (/ w 2.0)) y0 (- y (/ h 2.0)) y1 (+ y (/ h 2.0)))
    (command "_.PLINE" "_NON" (list x0 y0) "_NON" (list x1 y0) "_NON" (list x1 y1) "_NON" (list x0 y1) "_C")
    (setq obj (vlax-ename->vla-object (entlast))) (vla-put-Layer obj "SILICONE-CANDIDATE") (vla-put-Color obj 2)
    (vl-catch-all-apply 'vla-put-ConstantWidth (list obj 1.0))
    (setq obj (vla-AddText ms (strcat code "-" pane) (vlax-3d-point (list (+ x0 2.0) (+ y0 2.0) 0.0)) 8.0))
    (vla-put-Layer obj "SILICONE-CANDIDATE") (vla-put-Color obj 2))
  (close f) (setvar "CLAYER" oldlay) (setvar "OSMODE" oldos)
  (princ "\nSILCANDIDATES complete: yellow review polylines created.") (princ))
